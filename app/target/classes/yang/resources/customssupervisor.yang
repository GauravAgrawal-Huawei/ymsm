module customssupervisor {

    yang-version 1;

    namespace "ydt.customs-supervisor";

    prefix "customs";
    
    organization "ON-LAB";

    description "This module defines for customs-supervisor.";

    revision "2016-05-24" {
        description "Initial revision.";
    }

    leaf supervisor {
        type string;
        description "name of the customs-supervisor.";
    }
}

module YtbIetfSchedule {
    yang-version 1;
    namespace "yms:test:ytb:module:with:leaf:ietfschedule";
    prefix "sch";
    revision "2016-08-26";
        leaf time {
            type int8;
        }
    container monitor {
        leaf check {
            type uint8;
        }
    }
}
